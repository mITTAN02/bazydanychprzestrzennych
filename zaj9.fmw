FME workspace zaj9.fmw
Startup Python:
      import fme
      import smtplib
      from email.mime.text import MIMEText
      from email.mime.multipart import MIMEMultipart
      from datetime import datetime

      # Message variables
      curDate = datetime.now().strftime("%d.%m.%Y")
      curTime = datetime.now().strftime("%H:%M:%S")
      powiat = FME_MacroValues['POWIAT']

      # Email configuration
      sender_email = FME_MacroValues['E-MAIL']
      receiver_email = FME_MacroValues['KLIENT_E-MAIL']
      subject = "FME start"
      body = 'Drogi użytkowniku ' + receiver_email + ', o godzinie ' + curTime  + curDate + ' rozpoczęto przetwarzanie danych dla powiatu ' + powiat + '.'

      # SMTP server configuration
      smtp_server = "smtp.gmail.com"
      smtp_port = 587
      smtp_username = FME_MacroValues['E-MAIL']
      smtp_password = FME_MacroValues['HASLO']

      # Create a MIME object
      message = MIMEMultipart()
      message["From"] = sender_email
      message["To"] = receiver_email
      message["Subject"] = subject

      # Attach the body to the message
      message.attach(MIMEText(body, "plain"))

      # Connect to the SMTP server
      with smtplib.SMTP(smtp_server, smtp_port) as server:
          # Start the TLS connection
          server.starttls()

          # Log in to the email account
          server.login(smtp_username, smtp_password)

          # Send the email
          server.sendmail(sender_email, receiver_email, message.as_string())

      print("Email sent successfully!")
Shutdown Python:
      import fme
      import fmeobjects


      class FeatureProcessor(object):

          def __init__(self):
              pass

          def has_support_for(self, support_type: int):
              return support_type == fmeobjects.FME_SUPPORT_FEATURE_TABLE_SHIM

          def input(self, feature: fmeobjects.FMEFeature):
              self.pyoutput(feature)

          def close(self):
              pass

          def process_group(self):
              pass

Parameters:
- E-MAIL = mateusz.mitan@gmail.com   # Adres e-mail
- HASLO =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   # Hasło
- KLIENT_E-MAIL = mateusz.mitan@gmail.com   # Adres e-mail klienta
- POWIAT = powiat tatrzański   # Powiat
- MAX_POKRYCIE_CHMURAMI = 50   # Maksymalne pokrycie chmurami
- DATA_POCZATKOWA = 20230701000000   # Data początkowa
- DATA_KONCOWA = 20230731000001   # Data końcowa
- SourceDataset_SHAPEFILE = $(FME_MF_DIR)powiaty.shp   # Source Esri Shapefile(s)
- DestDataset_GEOTIFF = C:\Users\mateu\OneDrive\Pulpit\Bazy_danych_przestrzennych\Zadania\Zajecia9   # Destination GeoTIFF Folder

Readers:
- SHAPEFILE_1: SHAPEFILE from $(SourceDataset_SHAPEFILE)

Writers:
- GEOTIFF_1: GEOTIFF to $(DestDataset_GEOTIFF)

powiaty (reader SHAPEFILE_1)
    attributes: gml_id varchar(254), JPT_SJR_KO varchar(254), JPT_POWIER varchar(254), JPT_KOD_JE varchar(254), JPT_NAZWA_ varchar(254), JPT_ORGAN_ varchar(254), JPT_JOR_ID varchar(254), WERSJA_OD varchar(254), WERSJA_DO varchar(254), WAZNY_OD varchar(254), WAZNY_DO varchar(254), JPT_KOD__1 varchar(254), JPT_NAZWA1 varchar(254), JPT_ORGAN1 varchar(254), JPT_WAZNA_ varchar(254), ID_BUFORA_ varchar(254), ID_BUFORA1 varchar(254), ID_TECHNIC varchar(254), IIP_PRZEST varchar(254), IIP_IDENTY varchar(254), IIP_WERSJA varchar(254), JPT_KJ_IIP varchar(254), JPT_KJ_I_1 varchar(254), JPT_KJ_I_2 varchar(254), JPT_OPIS varchar(254), JPT_SPS_KO varchar(254), ID_BUFOR_1 varchar(254), JPT_ID varchar(254), JPT_POWI_1 varchar(254), JPT_KJ_I_3 varchar(254),
      JPT_GEOMET varchar(254), JPT_GEOM_1 varchar(254), SHAPE_LENG varchar(254), SHAPE_AREA varchar(254), REGON varchar(254), RODZAJ varchar(254)
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(JPT_NAZWA_) = $(POWIAT)",@Value(JPT_NAZWA_) = __POWIAT_
    @Value(JPT_NAZWA_) = __POWIAT_ -> Reprojector
Reprojector
    DEST = EPSG:4326
    INTERPOLATION_TYPE_NAME = Nearest Neighbor
    RASTER_CELL_SIZE = Preserve Cells
    RASTER_TOLERANCE = 0.0
    REPROJECTED -> Clipper [CLIPPER]
    REPROJECTED -> BoundingBoxAccumulator
BoundingBoxAccumulator
    ACCUM_ATTRS_NAME = Use Attributes From One Feature
    BOUNDING_BOX -> EarthCacheConnector
EarthCacheConnector
    api_key =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
    end_date = $(DATA_KONCOWA)
    interval = 7
    min_aoi_coverage_percentage = $(MAX_POKRYCIE_CHMURAMI)
    output_id = rgbn-a3e8-11e7-9793-ae4260ee3b4b
    pipeline_name = Sentinel2
    start_date = $(DATA_POCZATKOWA)
    -> Sampler
Sampler
    RATE = 1
    SAMPLE_MODE = No
    SAMPLE_TYPE_LONG = First N Features
    SAMPLED -> RasterBandSeparator
RasterBandSeparator
    BAND_INDEX_FIELD = _band_index
    PALETTE_INDEX_FIELD = _palette_index
    RASTER_INDEX_FIELD = _raster_index
    SPLIT_BY_NAME = Band and Palette
    -> TestFilter_2
    -> TestFilter_3
TestFilter_2
    DEFAULT_VALUE = <UNFILTERED>
    PASSED_TEST_GROUP_OUTPUT = FIRST
    TEST_LIST = "BOOL_OP,OR,COMPOSITE_TEST,""""""1"""""",TEST_CLAUSE,TEST @Value(_band_index) = 0",@Value(_band_index) = 0
    @Value(_band_index) = 0 -> NDVICalculator [Red]
TestFilter_3
    DEFAULT_VALUE = <UNFILTERED>
    PASSED_TEST_GROUP_OUTPUT = FIRST
    TEST_LIST = "BOOL_OP,OR,COMPOSITE_TEST,""""""1"""""",TEST_CLAUSE,TEST @Value(_band_index) = 3",@Value(_band_index) = 3
    @Value(_band_index) = 3 -> NDVICalculator [Infrared]
NDVICalculator
    COLORIZE = Blue-Yellow-Green Palette
    INDEXTYPE = NDVI
    SAVIADJUSTMENT = 0.5
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterStatisticsCalculator
    INSIDE -> powiaty (writer GEOTIFF_1)
RasterStatisticsCalculator
    RASTER_LEVEL = BAND_ONLY
    RASTER_STATS = "0   MEAN   STDEV   "
    -> Inspector
Inspector
powiaty (writer GEOTIFF_1)
    attributes: gml_id char(254), JPT_SJR_KO char(254), JPT_POWIER char(254), JPT_KOD_JE char(254), JPT_NAZWA_ char(254), JPT_ORGAN_ char(254), JPT_JOR_ID char(254), WERSJA_OD char(254), WERSJA_DO char(254), WAZNY_OD char(254), WAZNY_DO char(254), JPT_KOD__1 char(254), JPT_NAZWA1 char(254), JPT_ORGAN1 char(254), JPT_WAZNA_ char(254), ID_BUFORA_ char(254), ID_BUFORA1 char(254), ID_TECHNIC char(254), IIP_PRZEST char(254), IIP_IDENTY char(254), IIP_WERSJA char(254), JPT_KJ_IIP char(254), JPT_KJ_I_1 char(254), JPT_KJ_I_2 char(254), JPT_OPIS char(254), JPT_SPS_KO char(254), ID_BUFOR_1 char(254), JPT_ID char(254), JPT_POWI_1 char(254), JPT_KJ_I_3 char(254),
      JPT_GEOMET char(254), JPT_GEOM_1 char(254), SHAPE_LENG char(254), SHAPE_AREA char(254), REGON char(254), RODZAJ char(254)
